AGENTX-TEST-MIB DEFINITIONS ::= BEGIN

IMPORTS
    MODULE-IDENTITY, OBJECT-TYPE, Integer32, Counter64   FROM SNMPv2-SMI
    enterprises                                          FROM SNMPv2-SMI
    agentxObjects                                        FROM AGENTX-MIB
    ucdavis                                              FROM UCD-SNMP-MIB
    ;

agentxTestMIB MODULE-IDENTITY
    LAST-UPDATED "201401101330Z"
    ORGANIZATION "N/A"
    CONTACT-INFO "Editor: Max Kalika Email: max.kalika+projects@gmail.com"
    DESCRIPTION  "agentxTest"
    REVISION     "201401101330Z"
    DESCRIPTION  "autogenerated mib"
    ::= { ucdavis 1123 }

agentxTestString OBJECT-TYPE
    SYNTAX      OCTET STRING
    MAX-ACCESS  read-only
    STATUS      current
    DESCRIPTION "agentxTestString"
    ::= { agentxTestMIB 1 }

agentxTestInteger OBJECT-TYPE
    SYNTAX      Integer32
    MAX-ACCESS  read-only
    STATUS      current
    DESCRIPTION "agentxTestInteger"
    ::= { agentxTestMIB 2 }

agentxTestCounter OBJECT-TYPE
    SYNTAX      Counter64
    MAX-ACCESS  read-only
    STATUS      current
    DESCRIPTION "agentxTestCounter"
    ::= { agentxTestMIB 3 }

AgentxTestEntry ::= SEQUENCE {
    agentxTestTableIndex   Integer32,
    agentxTestTableString  OCTET STRING
    agentxTestTableInteger OCTET STRING
    agentxTestTableCounter OCTET STRING
}

agentxTestTable OBJECT-TYPE
    SYNTAX      SEQUENCE OF AgentxTestEntry
    MAX-ACCESS  not-accessible
    STATUS      current
    DESCRIPTION "AgentxTestTable"
    ::= { agentxTestMIB 4 }

agentxTestEntry OBJECT-TYPE
    SYNTAX      AgentxTestEntry
    MAX-ACCESS  not-accessible
    STATUS      current
    DESCRIPTION "AgentxTestEntry"
    INDEX       { agentxTestTableIndex }
    ::= { agentxTestTable 1 }

agentxTestTableString OBJECT-TYPE
    SYNTAX      OCTET STRING
    MAX-ACCESS  read-only
    STATUS      current
    DESCRIPTION "agentxTestTableString"
    ::= { agentxTestEntry 1 }

agentxTestTableInteger OBJECT-TYPE
    SYNTAX      Integer32
    MAX-ACCESS  read-only
    STATUS      current
    DESCRIPTION "agentxTestTableInteger"
    ::= { agentxTestEntry 2 }

agentxTestTableCounter OBJECT-TYPE
    SYNTAX      Counter64
    MAX-ACCESS  read-only
    STATUS      current
    DESCRIPTION "agentxTestTableCounter"
    ::= { agentxTestEntry 3 }

END
